## REQT01
- La température du SRI doit être maintenue entre 16°C et 30°C.

## REQV02
- Si la température dépasse ces limites, elle doit être revenue dans l'intervalle au bout d'une minute.

## REQQ03
- Afin de limiter les phénomènes d'érosion et de corrosion, la vitesse du fluide dans les échangeurs ne doit pas dépasser 6 m/s.
